/*
 * Copyright © 2016 Cisco Systems, Inc and others.  All rights reserved.
 *
 * This program and the accompanying materials are made available under the
 * terms of the Eclipse Public License v1.0 which accompanies this distribution,
 * and is available at http://www.eclipse.org/legal/epl-v10.html
 */

module sparkbot-commons {
    yang-version 1;
    namespace "urn:opendaylight:params:xml:ns:yang:sparkbot:commons";
    prefix "cmns";

    revision "2016-11-10" {
        description
            "Initial revision of type/grouping definitions used in all
            sparkbot service models";

    }

    typedef return-code {
        type enumeration {
            enum "OK" {
                value 0;
            }
            enum "INVALID-PARAMETER" {
                value 1;
            }
            enum "SPARK-OPER-ERROR" {
                value 2;
            }
       }
    }

    grouping return-status {
        leaf return-status {
            type cmns:return-code;
            description
                "Return status code from the REST call to Spark";
        }
        leaf error-message {
            when "./status-code != OK";
            type string;
            description
                "Error message describing the error if operation was
                not successful";
        }
    }
}
