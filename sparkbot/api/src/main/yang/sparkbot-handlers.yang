/*
 * Copyright © 2016 Cisco Systems, Inc and others.  All rights reserved.
 *
 * This program and the accompanying materials are made available under the
 * terms of the Eclipse Public License v1.0 which accompanies this distribution,
 * and is available at http://www.eclipse.org/legal/epl-v10.html
 */
module sparkbot-handlers {
    yang-version 1;
    namespace "urn:opendaylight:params:xml:ns:yang:sparkbot:handlers";
    prefix "hdlr";

    import sparkbot-commons { prefix cmns; }

    revision "2016-11-18" {
        description
            "Initial revision of the sparkbot test handler functions";
    }

    typedef handler-type {
        type enumeration {
            enum "RAW" {
                value 0;
            }
            enum "MESSAGES" {
                value 1;
            }
            enum "ROOMS" {
                value 2;
            }
            enum "MEMBERSHIPS" {
                value 3;
            }
       }
    }

    typedef resource-type {
        type enumeration {
            enum "MESSAGE" {
                value 0;
            }
            enum "ROOM" {
                value 1;
            }
            enum "MEMBERSHIP" {
                value 2;
            }
            enum "ALL" {
                value 3;
            }
        }
        default "ALL";
    }

    typedef event-type {
        type enumeration {
            enum "CREATED" {
                value 0;
            }
            enum "UPDATED" {
                value 1;
            }
            enum "DELETED" {
                value 2;
            }
            enum "ALL" {
                value 3;
            }
        }
        default "ALL";
    }

    rpc register-test-handler {
        description
            "Register with a WebHookServer a test handler of a given type.";
        input {
            leaf handler-type {
                type handler-type;
                description
                    "The type of the handler to register";
            }
            container filter {
                leaf name {
                    type string;
                    description
                        "Name";
                }
                leaf resource {
                    type resource-type;
                    description
                        "";
                }
                leaf event {
                    type event-type;
                    description
                        "";
                }
                leaf filter {
                    type string;
                    description
                        "The filter";
                }
                leaf secret {
                    type string;
                    description
                        "";
                }
            }
        }
        output {
            uses cmns:return-status;
        }
    }
    rpc unregister-test-handler {
        description
            "Unregister from a WebHookServer a test handler of a given
            type.";
        input {
            leaf handler-type {
                type handler-type;
                description
                    "The type of the handler to unregister";
            }
        }
        output {
            uses cmns:return-status;
        }
    }
}
